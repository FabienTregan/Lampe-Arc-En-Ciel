board(B) {

  int NB_SEGMENTS = 3;
  int NB_ROWS = 4;

  string script = "GRID MM; MARK (100 0);";

  for (int segment = 0; segment < NB_SEGMENTS; segment++){
    for (int row = 0; row < NB_ROWS; row++) {

      int n = (1 + segment * NB_ROWS + row); 
      string apa102;
      sprintf(apa102, "U$%d", n + 1);
      string cap;
      sprintf(cap, "C%d", n);

       
      string line;

      sprintf(line, "MOVE %s (R 0 0);\nROTATE =R270 %s;\n", apa102, apa102);
      script += line;

      sprintf(line, "MOVE %s (R -1.5 -5);\nROTATE =R180 %s;\n", cap, cap);
      script += line;

      real angle = 180/6 * (segment + 0.5);
      real rayon = 65 + row * 10;
      script += "GROUP (R 0 0) (RS -1.5 -5);\n";
      sprintf(line, "MOVE (R> 0 0) (R %f 0);\n", -rayon );
      script += line;
      sprintf(line, "ROTATE =R%f (RC> 0 0);", -angle );
      script += line;
    }
  }
   //dlgMessageBox(script);
   exit(script);
}
