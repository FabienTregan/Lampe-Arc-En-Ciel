UL_ELEMENT noElement;
UL_CONTACT noContact;

UL_ELEMENT findElement(string name) {

  board(B) {
    B.elements(E) {
      if (E.name == name) {
        return E;
      }
    }
  }

  string error;
  sprintf(error, "Element named '%s' not found.", name);
  dlgMessageBox(error);

  return noElement;
}

UL_CONTACT findContactFrom(UL_ELEMENT element, string name) {

  element.package.contacts(c) {
    if(c.name == name) {
      return c;
    }
  }

  string error;
  sprintf(error, "Contact named '%s' not found in element '%s'.", name, element.name);
  dlgMessageBox(error);

  return noContact;
}

UL_CONTACT findContact(string elementName, string contactName) {

  UL_ELEMENT e = findElement(elementName);
  UL_CONTACT c = findContactFrom(e, contactName);

  return c;
}
